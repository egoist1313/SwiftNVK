;;; nvk-dll.lsp — NETLOAD Nvk.Cad.dll
;;; Зависит от: nvk-config. *nvk-dir* задаёт nvk-load.lsp.
;;; Не определять nvk-ping здесь — это LispFunction из DLL.
;;;
;;; atoms-family на отсутствующее имя возвращает (nil), а не nil.
;;; Проверяем (car ...): иначе «функция есть» всегда, NETLOAD не вызывается.

;;; Выбор DLL: первый существующий файл из списка (от старшей версии к младшей).
;;; Timestamp не используется — порядок списка гарантирует выбор нужной версии.
(defun nvk-dll-put ( / kandidaty p k)
  (setq kandidaty
    (list
      (strcat *nvk-dir* "\\bin\\v156\\" *nvk-dll-name*)
      (strcat *nvk-dir* "\\bin\\v155\\" *nvk-dll-name*)
      (strcat *nvk-dir* "\\bin\\v154\\" *nvk-dll-name*)
      (strcat *nvk-dir* "\\bin\\v153\\" *nvk-dll-name*)
      (strcat *nvk-dir* "\\bin\\v152\\" *nvk-dll-name*)
      (strcat *nvk-dir* "\\bin\\v151\\" *nvk-dll-name*)
      (strcat *nvk-dir* "\\bin\\v150\\" *nvk-dll-name*)
      (strcat *nvk-dir* "\\bin\\v149\\" *nvk-dll-name*)
      (strcat *nvk-dir* "\\bin\\v148\\" *nvk-dll-name*)
      (strcat *nvk-dir* "\\bin\\v147\\" *nvk-dll-name*)
      (strcat *nvk-dir* "\\bin\\v146\\" *nvk-dll-name*)
      (strcat *nvk-dir* "\\bin\\v145\\" *nvk-dll-name*)
      (strcat *nvk-dir* "\\bin\\v144\\" *nvk-dll-name*)
      (strcat *nvk-dir* "\\bin\\v143\\" *nvk-dll-name*)
      (strcat *nvk-dir* "\\bin\\v142\\" *nvk-dll-name*)
      (strcat *nvk-dir* "\\bin\\v141\\" *nvk-dll-name*)
      (strcat *nvk-dir* "\\bin\\v140\\" *nvk-dll-name*)
      (strcat *nvk-dir* "\\bin\\v139\\" *nvk-dll-name*)
      (strcat *nvk-dir* "\\bin\\v138\\" *nvk-dll-name*)
      (strcat *nvk-dir* "\\bin\\v137\\" *nvk-dll-name*)
      (strcat *nvk-dir* "\\bin\\v136\\" *nvk-dll-name*)
      (strcat *nvk-dir* "\\bin\\v135\\" *nvk-dll-name*)
      (strcat *nvk-dir* "\\bin\\v134\\" *nvk-dll-name*)
      (strcat *nvk-dir* "\\bin\\v133\\" *nvk-dll-name*)
      (strcat *nvk-dir* "\\bin\\v132\\" *nvk-dll-name*)
      (strcat *nvk-dir* "\\bin\\v131\\" *nvk-dll-name*)
      (strcat *nvk-dir* "\\bin\\v130\\" *nvk-dll-name*)
      (strcat *nvk-dir* "\\bin\\v129\\" *nvk-dll-name*)
      (strcat *nvk-dir* "\\bin\\v128\\" *nvk-dll-name*)
      (strcat *nvk-dir* "\\bin\\v127\\" *nvk-dll-name*)
      (strcat *nvk-dir* "\\bin\\v126\\" *nvk-dll-name*)
      (strcat *nvk-dir* "\\bin\\v125\\" *nvk-dll-name*)
      (strcat *nvk-dir* "\\bin\\v124\\" *nvk-dll-name*)
      (strcat *nvk-dir* "\\bin\\v123\\" *nvk-dll-name*)
      (strcat *nvk-dir* "\\bin\\v122\\" *nvk-dll-name*)
      (strcat *nvk-dir* "\\bin\\v121\\" *nvk-dll-name*)
      (strcat *nvk-dir* "\\bin\\v120\\" *nvk-dll-name*)
      (strcat *nvk-dir* "\\bin\\v119\\" *nvk-dll-name*)
      (strcat *nvk-dir* "\\bin\\v118\\" *nvk-dll-name*)
      (strcat *nvk-dir* "\\bin\\v117\\" *nvk-dll-name*)
      (strcat *nvk-dir* "\\bin\\v116\\" *nvk-dll-name*)
      (strcat *nvk-dir* "\\bin\\v115\\" *nvk-dll-name*)
      (strcat *nvk-dir* "\\bin\\v114\\" *nvk-dll-name*)
      (strcat *nvk-dir* "\\bin\\v113\\" *nvk-dll-name*)
      (strcat *nvk-dir* "\\bin\\v112\\" *nvk-dll-name*)
      (strcat *nvk-dir* "\\bin\\v111\\" *nvk-dll-name*)
      (strcat *nvk-dir* "\\bin\\v110\\" *nvk-dll-name*)
      (strcat *nvk-dir* "\\bin\\v109\\" *nvk-dll-name*)
      (strcat *nvk-dir* "\\bin\\v108\\" *nvk-dll-name*)
      (strcat *nvk-dir* "\\bin\\v107\\" *nvk-dll-name*)
      (strcat *nvk-dir* "\\bin\\v106\\" *nvk-dll-name*)
      (strcat *nvk-dir* "\\bin\\v105\\" *nvk-dll-name*)
      (strcat *nvk-dir* "\\bin\\v104\\" *nvk-dll-name*)
      (strcat *nvk-dir* "\\bin\\v103\\" *nvk-dll-name*)
      (strcat *nvk-dir* "\\bin\\v102\\" *nvk-dll-name*)
      (strcat *nvk-dir* "\\bin\\v101\\" *nvk-dll-name*)
      (strcat *nvk-dir* "\\bin\\v100\\" *nvk-dll-name*)
      (strcat *nvk-dir* "\\bin\\v099\\" *nvk-dll-name*)
      (strcat *nvk-dir* "\\bin\\v098\\" *nvk-dll-name*)
      (strcat *nvk-dir* "\\bin\\v097\\" *nvk-dll-name*)
      (strcat *nvk-dir* "\\bin\\v096\\" *nvk-dll-name*)
      (strcat *nvk-dir* "\\bin\\v095\\" *nvk-dll-name*)
      (strcat *nvk-dir* "\\bin\\v094\\" *nvk-dll-name*)
      (strcat *nvk-dir* "\\bin\\v093\\" *nvk-dll-name*)
      (strcat *nvk-dir* "\\bin\\v092\\" *nvk-dll-name*)
      (strcat *nvk-dir* "\\bin\\v091\\" *nvk-dll-name*)
      (strcat *nvk-dir* "\\bin\\v090\\" *nvk-dll-name*)
      (strcat *nvk-dir* "\\bin\\v089\\" *nvk-dll-name*)
      (strcat *nvk-dir* "\\bin\\v088\\" *nvk-dll-name*)
      (strcat *nvk-dir* "\\bin\\v087\\" *nvk-dll-name*)
      (strcat *nvk-dir* "\\bin\\v086\\" *nvk-dll-name*)
      (strcat *nvk-dir* "\\bin\\v085\\" *nvk-dll-name*)
      (strcat *nvk-dir* "\\bin\\v084\\" *nvk-dll-name*)
      (strcat *nvk-dir* "\\bin\\v083\\" *nvk-dll-name*)
      (strcat *nvk-dir* "\\bin\\v082\\" *nvk-dll-name*)
      (strcat *nvk-dir* "\\bin\\v081\\" *nvk-dll-name*)
      (strcat *nvk-dir* "\\bin\\v080\\" *nvk-dll-name*)
      (strcat *nvk-dir* "\\bin\\v079\\" *nvk-dll-name*)
      (strcat *nvk-dir* "\\bin\\v078\\" *nvk-dll-name*)
      (strcat *nvk-dir* "\\bin\\v077\\" *nvk-dll-name*)
      (strcat *nvk-dir* "\\bin\\v076\\" *nvk-dll-name*)
      (strcat *nvk-dir* "\\bin\\v075\\" *nvk-dll-name*)
      (strcat *nvk-dir* "\\bin\\v074\\" *nvk-dll-name*)
      (strcat *nvk-dir* "\\bin\\v073\\" *nvk-dll-name*)
      (strcat *nvk-dir* "\\bin\\v072\\" *nvk-dll-name*)
      (strcat *nvk-dir* "\\bin\\v071\\" *nvk-dll-name*)
      (strcat *nvk-dir* "\\bin\\v070\\" *nvk-dll-name*)
      (strcat *nvk-dir* "\\bin\\v069\\" *nvk-dll-name*)
      (strcat *nvk-dir* "\\bin\\v068\\" *nvk-dll-name*)
      (strcat *nvk-dir* "\\bin\\v067\\" *nvk-dll-name*)
      (strcat *nvk-dir* "\\bin\\v066\\" *nvk-dll-name*)
      (strcat *nvk-dir* "\\bin\\v065\\" *nvk-dll-name*)
      (strcat *nvk-dir* "\\bin\\v064\\" *nvk-dll-name*)
      (strcat *nvk-dir* "\\bin\\v063\\" *nvk-dll-name*)
      (strcat *nvk-dir* "\\bin\\v062\\" *nvk-dll-name*)
      (strcat *nvk-dir* "\\bin\\v061\\" *nvk-dll-name*)
      (strcat *nvk-dir* "\\bin\\v060\\" *nvk-dll-name*)
      (strcat *nvk-dir* "\\bin\\v059\\" *nvk-dll-name*)
      (strcat *nvk-dir* "\\bin\\v058\\" *nvk-dll-name*)
      (strcat *nvk-dir* "\\bin\\v057\\" *nvk-dll-name*)
      (strcat *nvk-dir* "\\bin\\v056\\" *nvk-dll-name*)
      (strcat *nvk-dir* "\\bin\\v055\\" *nvk-dll-name*)
      (strcat *nvk-dir* "\\bin\\v054\\" *nvk-dll-name*)
      (strcat *nvk-dir* "\\bin\\v053\\" *nvk-dll-name*)
      (strcat *nvk-dir* "\\bin\\v052\\" *nvk-dll-name*)
      (strcat *nvk-dir* "\\bin\\v051\\" *nvk-dll-name*)
      (strcat *nvk-dir* "\\bin\\v050\\" *nvk-dll-name*)
      (strcat *nvk-dir* "\\bin\\v049\\" *nvk-dll-name*)
      (strcat *nvk-dir* "\\bin\\v048\\" *nvk-dll-name*)
      (strcat *nvk-dir* "\\bin\\v047\\" *nvk-dll-name*)
      (strcat *nvk-dir* "\\bin\\v046\\" *nvk-dll-name*)
      (strcat *nvk-dir* "\\bin\\v045\\" *nvk-dll-name*)
      (strcat *nvk-dir* "\\bin\\v044\\" *nvk-dll-name*)
      (strcat *nvk-dir* "\\bin\\v043\\" *nvk-dll-name*)
      (strcat *nvk-dir* "\\bin\\v042\\" *nvk-dll-name*)
      (strcat *nvk-dir* "\\bin\\v041\\" *nvk-dll-name*)
      (strcat *nvk-dir* "\\bin\\v040\\" *nvk-dll-name*)
      (strcat *nvk-dir* "\\bin\\v039\\" *nvk-dll-name*)
      (strcat *nvk-dir* "\\bin\\v038\\" *nvk-dll-name*)
      (strcat *nvk-dir* "\\bin\\v037\\" *nvk-dll-name*)
      (strcat *nvk-dir* "\\bin\\v036\\" *nvk-dll-name*)
      (strcat *nvk-dir* "\\bin\\v035\\" *nvk-dll-name*)
      (strcat *nvk-dir* "\\bin\\v034\\" *nvk-dll-name*)
      (strcat *nvk-dir* "\\bin\\v034\\" *nvk-dll-name*)
      (strcat *nvk-dir* "\\bin\\v033\\" *nvk-dll-name*)
      (strcat *nvk-dir* "\\bin\\v032\\" *nvk-dll-name*)
      (strcat *nvk-dir* "\\bin\\v031\\" *nvk-dll-name*)
      (strcat *nvk-dir* "\\bin\\v030\\" *nvk-dll-name*)
      (strcat *nvk-dir* "\\bin\\v029\\" *nvk-dll-name*)
      (strcat *nvk-dir* "\\bin\\v028\\" *nvk-dll-name*)
      (strcat *nvk-dir* "\\bin\\v027\\" *nvk-dll-name*)
      (strcat *nvk-dir* "\\bin\\v026\\" *nvk-dll-name*)
      (strcat *nvk-dir* "\\bin\\v025\\" *nvk-dll-name*)
      (strcat *nvk-dir* "\\bin\\v024\\" *nvk-dll-name*)
      (strcat *nvk-dir* "\\bin\\v023\\" *nvk-dll-name*)
      (strcat *nvk-dir* "\\bin\\v022\\" *nvk-dll-name*)
      (strcat *nvk-dir* "\\bin\\v020\\" *nvk-dll-name*)
      (strcat *nvk-dir* "\\bin\\net8\\" *nvk-dll-name*)
      (strcat *nvk-dir* "\\bin\\" *nvk-dll-name*)
      (strcat *nvk-dir* "\\src\\csharp\\Nvk.Cad.2025\\out_build\\" *nvk-dll-name*)
      (strcat *nvk-dir* "\\src\\csharp\\Nvk.Cad.2025\\bin\\Release\\net8.0-windows\\" *nvk-dll-name*)
      (strcat *nvk-dir* "\\src\\csharp\\Nvk.Cad.2025\\bin\\Debug\\net8.0-windows\\" *nvk-dll-name*)))
  (setq p nil)
  (foreach k kandidaty
    (if (and (null p) (findfile k))
      (setq p k)))
  p)

(defun nvk-dll-est-p ( / a)
  (setq a (atoms-family 1 '("NVK-PING")))
  (and a (car a) T))

(defun nvk-root-send ( )
  (if (and *nvk-dir* (car (atoms-family 1 '("NVK-ROOT"))))
    (vl-catch-all-apply 'nvk-root (list *nvk-dir*))))

(defun nvk-dll-svezhaya-p (s)
  (and s (= (type s) 'STR) (vl-string-search *nvk-versija* s)))

(defun nvk-dll-zagruzit ( / put old-fdia old-echo err s)
  (if (nvk-dll-est-p)
    (progn
      (setq s (nvk-dll-ping-stroka)
            *nvk-dll-ok* T)
      (nvk-root-send)
      (if (nvk-dll-svezhaya-p s)
        (progn (princ (strcat "\n[НВК] DLL на связи: " s)) T)
        (progn
          (princ (strcat "\n[НВК] в памяти: " s))
          (princ (strcat "\n[НВК] !!! нужна " *nvk-versija* ". Закрой Civil ПОЛНОСТЬЮ и load снова."))
          nil)))
    (progn
      (setq put (nvk-dll-put))
      (if (null put)
        (progn
          (princ "\n[НВК] DLL не найдена. Собери: dotnet build src\\csharp\\Nvk.sln -c Release")
          (setq *nvk-dll-ok* nil)
          nil)
        (progn
          (princ (strcat "\n[НВК] NETLOAD " put))
          (setq old-fdia (getvar "FILEDIA")
                old-echo (getvar "CMDECHO"))
          (setvar "FILEDIA" 0)
          (setvar "CMDECHO" 0)
          ;; command-s — вложенный вызов из НВК-ИНФО; иначе AutoCAD орёт «команда активна».
          (setq err
            (if (and (boundp 'command-s) (car (atoms-family 1 '("COMMAND-S"))))
              (vl-catch-all-apply 'command-s (list "._NETLOAD" put))
              (vl-catch-all-apply 'vl-cmdf (list "._NETLOAD" put))))
          (setvar "FILEDIA" old-fdia)
          (setvar "CMDECHO" old-echo)
          (if (vl-catch-all-error-p err)
            (princ (strcat "\n[НВК] NETLOAD ошибка: " (vl-catch-all-error-message err))))
          (setq *nvk-dll-ok* (nvk-dll-est-p))
          (if *nvk-dll-ok*
            (progn
              (nvk-root-send)
              (vl-catch-all-apply 'nvk-ui-otdat nil)
              (princ "\n[НВК] DLL на связи."))
            (princ "\n[НВК] NETLOAD прошёл, но NVK-PING не виден. Перезапусти AutoCAD и load снова."))
          *nvk-dll-ok*)))))

(defun nvk-dll-ping-stroka ( / r)
  (cond
    ((not (nvk-dll-est-p))
     (setq *nvk-dll-ok* nil)
     "DLL не загружена")
    (t
     (setq *nvk-dll-ok* T)
     (setq r (vl-catch-all-apply 'nvk-ping nil))
     (cond
       ((vl-catch-all-error-p r) (vl-catch-all-error-message r))
       ((null r) "nvk-ping = nil")
       (t (vl-princ-to-string r))))))

(defun C:НВК-DLL ( / )
  (nvk-dll-zagruzit)
  (princ (strcat "\n[НВК] " (nvk-dll-ping-stroka)))
  (princ))

(princ "\n  nvk-dll.lsp")
(princ)
