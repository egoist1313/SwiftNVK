;;; nvk-nod.lsp — память участка в NOD чертежа (словарь NVK)
;;; Трубы — список handle. Точки вставки, TIN, настройки.

(defun nvk-nod-dict (sozdat / nod d)
  (setq nod (namedobjdict))
  (setq d (dictsearch nod "NVK"))
  (cond
    (d (cdr (assoc -1 d)))
    (sozdat
     (setq d (entmakex '((0 . "DICTIONARY") (100 . "AcDbDictionary"))))
     (if d (dictadd nod "NVK" d))
     d)
    (t nil)))

(defun nvk-seg-key (s)
  (if (or (null s) (= s ""))
    "X"
    (vl-string-translate
      " ~`!@#$%^&*()+=[]{}\\|;:'\",.<>/?"
      "_______________________________"
      (strcase s))))

;; DXF код 1 — максимум 255 символов. Длинный SCATTER иначе валит весь XRECORD.
(defun nvk-nod-chunks (k v / lim out n chunk prefix)
  (setq v (if v v "")  lim 240  out nil  n 1)
  (if (<= (strlen (strcat k "=" v)) lim)
    (list (strcat k "=" v))
    (progn
      (while (> (strlen v) 0)
        (setq prefix (if (= n 1) k (strcat k "#" (itoa n)))
              chunk (substr v 1 (max 1 (- lim (strlen prefix) 1)))
              v (if (> (strlen v) (strlen chunk)) (substr v (1+ (strlen chunk))) "")
              out (append out (list (strcat prefix "=" chunk)))
              n (1+ n)))
      out)))

(defun nvk-nod-pisat-key (key alist / dict xd old pairs p rec s)
  (setq dict (nvk-nod-dict T))
  (if (null dict)
    nil
    (progn
      (setq pairs (list '(0 . "XRECORD") '(100 . "AcDbXrecord")))
      (foreach p alist
        (foreach s (nvk-nod-chunks (car p) (cdr p))
          (setq pairs (append pairs (list (cons 1 s))))))
      (setq rec (entmakex pairs))
      (if rec
        (progn
          (setq xd (dictsearch dict key))
          (if xd (entdel (cdr (assoc -1 xd))))
          (dictadd dict key rec)
          T)
        (progn
          (princ (strcat "\n[НВК] NOD не записан (" key "), старое состояние оставлено"))
          nil)))))

(defun nvk-nod-pisat (alist)
  (nvk-nod-pisat-key "STATE" alist)
  (if (and *nvk-seg-id* (> (strlen *nvk-seg-id*) 0))
    (nvk-nod-pisat-key (strcat "S_" (nvk-seg-key *nvk-seg-id*)) alist))
  T)

(defun nvk-xrec-alist (ed / result item s pos)
  (setq result nil)
  (if ed
    (foreach item ed
      (if (= (car item) 1)
        (progn
          (setq s (cdr item)  pos (vl-string-search "=" s))
          (if pos
            (setq result
              (cons (cons (substr s 1 pos) (substr s (+ pos 2))) result)))))))
  result)

(defun nvk-nod-chitat ( / dict xd ed result item s pos k v)
  (setq dict (nvk-nod-dict nil)  result nil)
  (if (null dict)
    nil
    (progn
      (setq xd (dictsearch dict "STATE"))
      (if xd
        (foreach item xd
          (if (= (car item) 1)
            (progn
              (setq s (cdr item)  pos (vl-string-search "=" s))
              (if pos
                (setq result
                  (cons (cons (substr s 1 pos)
                              (substr s (+ pos 2)))
                        result)))))))
      result)))

(defun nvk-nod-get-one (alist key / p)
  (setq p (assoc key alist))
  (if p (cdr p)
    (progn
      (setq p (assoc (strcase key) alist))
      (if p (cdr p)
        (progn
          (foreach x alist
            (if (and (null p) (eq (type (car x)) 'STR)
                     (equal (strcase (car x)) (strcase key)))
              (setq p x)))
          (if p (cdr p) nil))))))

(defun nvk-nod-get (alist key / v n extra)
  (setq v (nvk-nod-get-one alist key) n 2)
  (while (setq extra (nvk-nod-get-one alist (strcat key "#" (itoa n))))
    (setq v (strcat (if v v "") extra)
          n (1+ n)))
  v)

(defun nvk-nod-get-any (alist keys / k v)
  (setq v nil)
  (foreach k keys
    (if (null v) (setq v (nvk-nod-get alist k))))
  v)

(defun nvk-nod-xrec-str (ed / s)
  (setq s nil)
  (foreach item ed
    (if (and (null s) (member (car item) '(1 300 3)) (eq (type (cdr item)) 'STR))
      (setq s (cdr item))))
  s)

;;; PB_CS_LAYOUT — точки вставки сечений PipeBuild (MAIN, L1..L5).
(defun nvk-pb-nod-pt (key / nod d dict entry ed s p)
  (setq nod (namedobjdict)
        d   (dictsearch nod "PB_CS_LAYOUT"))
  (if (null d)
    nil
    (progn
      (setq dict (cdr (assoc -1 d))
            entry (dictsearch dict key))
      (if (null entry)
        nil
        (progn
          (setq ed (entget (cdr (assoc -1 entry)))
                s  (nvk-nod-xrec-str ed))
          (if (null s)
            nil
            (progn
              (setq p (vl-string-search "," s))
              (if p
                (list (atof (substr s 1 p)) (atof (substr s (+ p 2))))
                nil))))))))

;;; XData PIPEBLD на объекте: список dotted 1000/1040.
(defun nvk-pb-xd (en / xl xd)
  (if (null en)
    nil
    (progn
      (vl-catch-all-apply 'regapp (list "PIPEBLD"))
      (setq xl (assoc -3 (entget en '("PIPEBLD"))))
      (if xl (cdr (assoc "PIPEBLD" (cdr xl))) nil))))

(defun nvk-pb-xd-tag (xd prefix / item s n r)
  (setq r nil  n (strlen prefix))
  (foreach item xd
    (if (and (null r) (= (car item) 1000) (eq (type (cdr item)) 'STR))
      (progn
        (setq s (cdr item))
        (if (and (>= (strlen s) n) (equal (substr s 1 n) prefix))
          (setq r (substr s (1+ n)))))))
  r)

(defun nvk-pb-find-main ( / ss i n en xd tag found)
  (vl-catch-all-apply 'regapp (list "PIPEBLD"))
  (setq ss (ssget "X" '((-3 ("PIPEBLD"))))  found nil)
  (if ss
    (progn
      (setq i 0 n (sslength ss))
      (while (and (< i n) (null found))
        (setq en (ssname ss i)
              xd (nvk-pb-xd en))
        (if xd
          (progn
            (setq tag nil)
            (foreach item xd
              (if (and (= (car item) 1000) (equal (cdr item) "PIPEBLD_PROFILE"))
                (setq tag T)))
            (if (and tag (null (nvk-pb-xd-tag xd "RAZRTYPE:")))
              (setq found en))))
        (setq i (1+ i)))))
  found)

(defun nvk-lpts-empty-p (lst / x e)
  (setq e T)
  (foreach x lst (if x (setq e nil)))
  e)

(defun nvk-lpts-from-keys (keys / r k)
  (setq r nil)
  (foreach k keys
    (setq r (append r (list (nvk-pb-nod-pt k)))))
  r)

;; PB CS_L*_1 — левый край ряда; центр сечения = X + hw * l_scale (pc-build-all).
(defun nvk-lpts-pb-to-center (lst / off r p)
  (setq off (* (if *nvk-cs-hwidth* *nvk-cs-hwidth* 3.0)
               (if (and *nvk-l-scale* (> *nvk-l-scale* 0.0)) *nvk-l-scale* 1.0))
        r nil)
  (foreach p lst
    (setq r (append r (list (if p (list (+ (car p) off) (cadr p)) nil)))))
  r)

(defun nvk-lpts-str (lst / r p)
  (setq r "")
  (foreach p lst
    (setq r
      (strcat (if (= r "") "" (strcat r ";"))
              (if p (strcat (nvk-rtos-safe (car p)) "," (nvk-rtos-safe (cadr p))) ""))))
  r)

(defun nvk-lpts-parse (s / r tok p)
  (setq r nil)
  (if (and s (> (strlen s) 0))
    (foreach tok (nvk-split s ";")
      (setq p (vl-string-search "," tok))
      (if (and p (> (strlen tok) 2))
        (setq r (append r (list (list (atof (substr tok 1 p)) (atof (substr tok (+ p 2)))))))
        (setq r (append r (list nil))))))
  (while (< (length r) 5) (setq r (append r (list nil))))
  r)

(defun nvk-layout-send ( / a p)
  (if (null *nvk-ep-lpts*) (setq *nvk-ep-lpts* (list nil nil nil nil nil)))
  (if (null *nvk-cs-lpts*) (setq *nvk-cs-lpts* (list nil nil nil nil nil)))
  (setq a nil)
  (foreach p (append *nvk-ep-lpts* *nvk-cs-lpts*)
    (if p
      (setq a (append a (list (car p) (cadr p))))
      (setq a (append a (list 1.0e20 1.0e20)))))
  (vl-catch-all-apply 'nvk-layout-put a))

(defun nvk-lpts-put (lst i pt / n r x)
  (setq n 0 r nil)
  (foreach x lst
    (setq r (append r (list (if (= n i) pt x)))
          n (1+ n)))
  r)

(defun nvk-layout-pull ( / a key x y i)
  (setq a (vl-catch-all-apply 'nvk-layout-get nil))
  (if (or (null a) (vl-catch-all-error-p a) (not (listp a)))
    nil
    (progn
      (if (null *nvk-ep-lpts*) (setq *nvk-ep-lpts* (list nil nil nil nil nil)))
      (if (null *nvk-cs-lpts*) (setq *nvk-cs-lpts* (list nil nil nil nil nil)))
      (while (>= (length a) 3)
        (setq key (car a) x (cadr a) y (caddr a) a (cdddr a))
        (if (and (eq (type key) 'STR) (numberp x) (numberp y))
          (progn
            (setq i (atoi (substr key 3)))
            (if (and (>= i 1) (<= i 5))
              (if (wcmatch (strcase key) "EP*")
                (setq *nvk-ep-lpts* (nvk-lpts-put *nvk-ep-lpts* (1- i) (list x y)))
                (setq *nvk-cs-lpts* (nvk-lpts-put *nvk-cs-lpts* (1- i) (list x y))))))))
      T)))

(defun nvk-nod-import-pb (had / pt en xd hs reals item s ss h pb-cs)
  (if (null *nvk-ep-lpts*) (setq *nvk-ep-lpts* (list nil nil nil nil nil)))
  (if (null *nvk-cs-lpts*) (setq *nvk-cs-lpts* (list nil nil nil nil nil)))
  (if (null *nvk-ep-ins*)
    (progn
      (setq pt (nvk-pb-nod-pt "MAIN"))
      (if pt (setq *nvk-ep-ins* pt))))
  (if (nvk-lpts-empty-p *nvk-ep-lpts*)
    (setq *nvk-ep-lpts* (nvk-lpts-from-keys '("L1" "L2" "L3" "L4" "L5"))))
  (setq pb-cs nil)
  (if (nvk-lpts-empty-p *nvk-cs-lpts*)
    (progn
      (setq *nvk-cs-lpts* (nvk-lpts-from-keys '("CS_L1_1" "CS_L2_1" "CS_L3_1" "CS_L4_1" "CS_L5_1")))
      (if (not (nvk-lpts-empty-p *nvk-cs-lpts*))
        (setq pb-cs T))))
  (if (null *nvk-vol-ins*)
    (if *nvk-ep-ins*
      (setq *nvk-vol-ins* (list (car *nvk-ep-ins*) (- (cadr *nvk-ep-ins*) 40.0)))))
  (setq en (nvk-pb-find-main))
  (if en
    (progn
      (setq xd (nvk-pb-xd en)  hs nil  reals nil)
      (foreach item xd
        (cond
          ((and (= (car item) 1000) (eq (type (cdr item)) 'STR)
                (>= (strlen (cdr item)) 5)
                (equal (substr (cdr item) 1 5) "PIPE:"))
           (setq hs (append hs (list (substr (cdr item) 6)))))
          ((= (car item) 1040)
           (setq reals (append reals (list (cdr item)))))))
      (if (and reals (>= (length reals) 7) (null *nvk-ep-ins*))
        (setq *nvk-ep-ins* (list (nth 5 reals) (nth 6 reals))))
      (if (and reals (>= (length reals) 4) (null had))
        (progn
          (setq *nvk-h-scale* (nth 1 reals)
                *nvk-l-scale* (nth 2 reals)
                *nvk-text-h*  (nth 3 reals)
                *nvk-cs-scale* *nvk-l-scale*)))
      (setq s (nvk-pb-xd-tag xd "BEDDING:"))
      (if (and s (null had)) (setq *nvk-bedding* (atof s)))
      (setq s (nvk-pb-xd-tag xd "ZASHITA_THK:"))
      (if (and s (null had)) (setq *nvk-thk-zash* (atof s)))
      (setq s (nvk-pb-xd-tag xd "CS_JOINT:"))
      (if (and s (> (strlen s) 0) (null had)) (setq *nvk-joint* s))
      (setq s (nvk-pb-xd-tag xd "CS_HWIDTH:"))
      (if (and s (null had)) (setq *nvk-cs-hwidth* (atof s)))
      (setq s (nvk-pb-xd-tag xd "CS_SLOPE:"))
      (if (and s (null had)) (setq *nvk-cs-slope* (atof s)))
      (setq s (nvk-pb-xd-tag xd "CS_TEXT_H:"))
      (if (and s (null had)) (setq *nvk-cs-text-h* (atof s)))
      (setq s (nvk-pb-xd-tag xd "CS_YGAP:"))
      (if (and s (null had)) (setq *nvk-cs-ygap* (atof s)))
      (setq s (nvk-pb-xd-tag xd "CS_STATIONS:"))
      (if (and s (> (strlen s) 0) (null had)) (setq *nvk-stations-str* s))
      (setq s (nvk-pb-xd-tag xd "SURF:"))
      (if (and s (null *nvk-surf-handle*))
        (progn
          (setq *nvk-surf-handle* s)
          (if (handent s)
            (vl-catch-all-apply
              '(lambda ( / o)
                 (setq o (vlax-ename->vla-object (handent s)))
                 (setq *nvk-surf-name* (vla-get-name o)))))))
      (if (and hs (or (null *nvk-pipe-ss*) (= (sslength *nvk-pipe-ss*) 0)))
        (progn
          (setq ss nil)
          (foreach h hs
            (setq en (handent h))
            (if en (setq ss (if ss (progn (ssadd en ss) ss) (ssadd en)))))
          (if ss (setq *nvk-pipe-ss* ss))))))
  (if pb-cs
    (setq *nvk-cs-lpts* (nvk-lpts-pb-to-center *nvk-cs-lpts*)))
  (if (null *nvk-cs-ins*)
    (progn
      (setq pt (car *nvk-cs-lpts*))
      (if pt (setq *nvk-cs-ins* pt))))
  (if (or *nvk-ep-ins* *nvk-cs-ins* *nvk-pipe-ss*)
    (princ "\n[НВК] подхвачен старый NOD PB_CS_LAYOUT / PIPEBLD"))
  T)

(defun nvk-pipes-key (s)
  (if (or (null s) (= s ""))
    ""
    (nvk-join
      (vl-sort
        (vl-remove "" (mapcar 'strcase (nvk-split s ";")))
        '<)
      ";")))

(defun nvk-nod-podhvat-po-trubam ( / hs dict item name ed a pipes found)
  (setq hs (nvk-join (nvk-pipe-handles) ";")
        found nil)
  (if (or (null hs) (= hs ""))
    nil
    (progn
      (setq dict (nvk-nod-dict nil))
      (if dict
        (foreach item (entget dict)
          (if (and (null found) (= (car item) 3)
                   (wcmatch (strcase (cdr item)) "S_*"))
            (progn
              (setq name (cdr item)
                    ed (dictsearch dict name)
                    a (nvk-xrec-alist ed)
                    pipes (nvk-pipes-key (if (nvk-nod-get a "PIPES") (nvk-nod-get a "PIPES") "")))
              (if (and a (equal pipes hs))
                (setq found a))))))
      (if found
        (progn
          (nvk-nod-pisat-key "STATE" found)
          (nvk-nod-zagruzit)
          T)
        nil))))

(defun nvk-rtos-safe (x)
  (if (and x (numberp x)) (rtos x 2 4) ""))

(defun nvk-pipe-handles ( / i n en h lst)
  (setq lst nil)
  (if (and *nvk-pipe-ss* (> (sslength *nvk-pipe-ss*) 0))
    (progn
      (setq i 0 n (sslength *nvk-pipe-ss*))
      (while (< i n)
        (setq en (ssname *nvk-pipe-ss* i)
              h  (if en (cdr (assoc 5 (entget en))) nil))
        (if h (setq lst (append lst (list (strcase h)))))
        (setq i (1+ i)))))
  (if lst (vl-sort lst '<) lst))

(defun nvk-join (lst sep / r)
  (setq r "")
  (foreach x lst
    (setq r (if (= r "") x (strcat r sep x))))
  r)

(defun nvk-split (s sep / p r rest)
  (setq r nil  rest s)
  (while rest
    (setq p (vl-string-search sep rest))
    (if p
      (progn
        (setq r (append r (list (substr rest 1 p))))
        (setq rest (substr rest (+ p 1 (strlen sep)))))
      (progn (setq r (append r (list rest))  rest nil))))
  r)

(defun nvk-nod-sohranit ( / hs cache)
  (setq hs (nvk-pipe-handles))
  (setq cache (vl-catch-all-apply 'nvk-cache-get nil))
  (if (and cache (not (vl-catch-all-error-p cache)) (listp cache))
    (let ((sv (nvk-plist-get cache "SCATTER"))
          (s2 (nvk-plist-get cache "SCATTER2"))
          (s3 (nvk-plist-get cache "SCATTER3"))
          (s4 (nvk-plist-get cache "SCATTER4"))
          (s5 (nvk-plist-get cache "SCATTER5"))
          (lv (nvk-plist-get cache "LATOFF"))
          (tv (nvk-plist-get cache "PLAN_TGT"))
          (pv (nvk-plist-get cache "PLAN_LAT")))
      (if (and sv (> (strlen sv) 0)) (setq *nvk-scatter-vals* sv))
      (if (and s2 (> (strlen s2) 0)) (setq *nvk-scatter-l2* s2))
      (if (and s3 (> (strlen s3) 0)) (setq *nvk-scatter-l3* s3))
      (if (and s4 (> (strlen s4) 0)) (setq *nvk-scatter-l4* s4))
      (if (and s5 (> (strlen s5) 0)) (setq *nvk-scatter-l5* s5))
      (if (and lv (> (strlen lv) 0)) (setq *nvk-latoff-vals* lv))
      (if (and tv (> (strlen tv) 0)) (setq *nvk-plan-tgt* tv))
      (if (and pv (> (strlen pv) 0)) (setq *nvk-plan-lat* pv))))
  (nvk-nod-pisat
    (list
      (cons "BEDDING"   (nvk-rtos-safe *nvk-bedding*))
      (cons "THK_ZASH"  (nvk-rtos-safe *nvk-thk-zash*))
      (cons "THK_ASPH"  (nvk-rtos-safe *nvk-thk-asph*))
      (cons "THK_GAZN"  (nvk-rtos-safe *nvk-thk-gazn*))
      (cons "THK_TROT"  (nvk-rtos-safe *nvk-thk-trot*))
      (cons "THK_OTHER" (nvk-rtos-safe *nvk-thk-other*))
      (cons "FILL_ASPH"  (if *nvk-fill-asph* *nvk-fill-asph* "SAND"))
      (cons "FILL_TROT"  (if *nvk-fill-trot* *nvk-fill-trot* "SAND"))
      (cons "FILL_GAZN"  (if *nvk-fill-gazn* *nvk-fill-gazn* "SOIL"))
      (cons "FILL_OTHER" (if *nvk-fill-other* *nvk-fill-other* "SOIL"))
      (cons "USE_BE"    (if *nvk-use-black-earth* "1" "0"))
      (cons "BE_H"      (if *nvk-black-earth-h* *nvk-black-earth-h* ""))
      (cons "BE_N"      (if *nvk-black-earth-n* *nvk-black-earth-n* ""))
      (cons "L1_MH"     (if *nvk-l1-mh* "1" "0"))
      (cons "TBL_OFF"   (nvk-rtos-safe *nvk-table-off-m*))
      (cons "L1_PRESET" (if *nvk-l1-preset* *nvk-l1-preset* "default"))
      (cons "PAV_ALL"   (if *nvk-pav-all* "1" "0"))
      (cons "ZONES"     (if *nvk-zones-str* *nvk-zones-str* ""))
      (cons "USE_WALL"  (if *nvk-use-wall* "1" "0"))
      (cons "WALLS"     (if *nvk-wall-str* *nvk-wall-str* ""))
      (cons "PROJ_FACT" (if *nvk-proj-fact* "1" "0"))
      (cons "SINGLE_SC" (if *nvk-single-scatter* "1" "0"))
      (cons "USE_SC_R"  (if *nvk-use-sc-r* "1" "0"))
      (cons "USE_SC_T"  (if *nvk-use-sc-t* "1" "0"))
      (cons "USE_SC_Z"  (if *nvk-use-sc-z* "1" "0"))
      (cons "USE_SC_S"  (if *nvk-use-sc-s* "1" "0"))
      (cons "SC_R"      (nvk-rtos-safe *nvk-sc-r*))
      (cons "SC_T"      (nvk-rtos-safe *nvk-sc-t*))
      (cons "SC_Z"      (nvk-rtos-safe *nvk-sc-z*))
      (cons "SC_S"      (nvk-rtos-safe *nvk-sc-s*))
      (cons "ANNOT"     (if *nvk-annotative* "1" "0"))
      (cons "ANN_GAP"   (nvk-rtos-safe *nvk-ann-gap*))
      (cons "PLAN_EN"   (if *nvk-plan-en* "1" "0"))
      (cons "PLAN_INT"  (nvk-rtos-safe *nvk-plan-int*))
      (cons "PLAN_MIN"  (nvk-rtos-safe *nvk-plan-min*))
      (cons "DRAW_PROJ" (if *nvk-draw-proj* "1" "0"))
      (cons "DELTA_H"   (if *nvk-delta-h* "1" "0"))
      (cons "SCATTER"   (if *nvk-scatter-vals* *nvk-scatter-vals* ""))
      (cons "SCATTER2"  (if *nvk-scatter-l2* *nvk-scatter-l2* ""))
      (cons "SCATTER3"  (if *nvk-scatter-l3* *nvk-scatter-l3* ""))
      (cons "SCATTER4"  (if *nvk-scatter-l4* *nvk-scatter-l4* ""))
      (cons "SCATTER5"  (if *nvk-scatter-l5* *nvk-scatter-l5* ""))
      (cons "LATOFF"    (if *nvk-latoff-vals* *nvk-latoff-vals* ""))
      (cons "PLAN_TGT"  (if *nvk-plan-tgt* *nvk-plan-tgt* ""))
      (cons "PLAN_LAT"  (if *nvk-plan-lat* *nvk-plan-lat* ""))
      (cons "JOINT"     (if *nvk-joint* *nvk-joint* "SOCKET"))
      (cons "CS_SLOPE"  (nvk-rtos-safe *nvk-cs-slope*))
      (cons "CS_SCALE"  (nvk-rtos-safe *nvk-cs-scale*))
      (cons "CS_YGAP"   (nvk-rtos-safe *nvk-cs-ygap*))
      (cons "CS_COLS"   (itoa (if *nvk-cs-cols* *nvk-cs-cols* 2)))
      (cons "H_SCALE"   (nvk-rtos-safe *nvk-h-scale*))
      (cons "L_SCALE"   (nvk-rtos-safe *nvk-l-scale*))
      (cons "STATIONS"  (if *nvk-stations-str* *nvk-stations-str* "AUTO"))
      (cons "BLOCK_CS"  (if *nvk-block-cs* "1" "0"))
      (cons "BLOCK_EP"  (if *nvk-block-ep* "1" "0"))
      (cons "SHOW_TAGS" (if *nvk-show-tags* "1" "0"))
      (cons "HWIDTH"    (nvk-rtos-safe *nvk-cs-hwidth*))
      (cons "TEXT_H"    (nvk-rtos-safe *nvk-text-h*))
      (cons "CS_TH"     (nvk-rtos-safe *nvk-cs-text-h*))
      (cons "TEXT_OFF"  (nvk-rtos-safe *nvk-text-off*))
      (cons "ROUND_TO"  (itoa (if *nvk-round-to* *nvk-round-to* 2)))
      (cons "SLOPE_RND" (itoa (if *nvk-slope-round* *nvk-slope-round* 1)))
      (cons "SLOPE_U"   (if *nvk-slope-unit* *nvk-slope-unit* "permille"))
      (cons "SHOW_PERM" (if *nvk-show-permille* "1" "0"))
      (cons "SHOW_LEN"  (if *nvk-show-len* "1" "0"))
      (cons "SHOW_SLP"  (if *nvk-show-slope* "1" "0"))
      (cons "LAB_W"     (nvk-rtos-safe *nvk-label-col-w*))
      (cons "SURF_H"    (if *nvk-surf-handle* *nvk-surf-handle* ""))
      (cons "SURF_N"    (if *nvk-surf-name* *nvk-surf-name* ""))
      (cons "CS_X"      (if *nvk-cs-ins* (nvk-rtos-safe (car *nvk-cs-ins*)) ""))
      (cons "CS_Y"      (if *nvk-cs-ins* (nvk-rtos-safe (cadr *nvk-cs-ins*)) ""))
      (cons "EP_X"      (if *nvk-ep-ins* (nvk-rtos-safe (car *nvk-ep-ins*)) ""))
      (cons "EP_Y"      (if *nvk-ep-ins* (nvk-rtos-safe (cadr *nvk-ep-ins*)) ""))
      (cons "VOL_X"     (if *nvk-vol-ins* (nvk-rtos-safe (car *nvk-vol-ins*)) ""))
      (cons "VOL_Y"     (if *nvk-vol-ins* (nvk-rtos-safe (cadr *nvk-vol-ins*)) ""))
      (cons "EP_LVLS"   (nvk-lpts-str *nvk-ep-lpts*))
      (cons "CS_LVLS"   (nvk-lpts-str *nvk-cs-lpts*))
      (cons "TBL_ROWS_L1" (if *nvk-rows-l1* *nvk-rows-l1* ""))
      (cons "TBL_ROWS_L2" (if *nvk-rows-l2* *nvk-rows-l2* ""))
      (cons "TBL_ROWS_L3" (if *nvk-rows-l3* *nvk-rows-l3* ""))
      (cons "TBL_ROWS_L4" (if *nvk-rows-l4* *nvk-rows-l4* ""))
      (cons "TBL_ROWS_L5" (if *nvk-rows-l5* *nvk-rows-l5* ""))
      (cons "FACT_PROF_L1" (if *nvk-fact-prof-l1* *nvk-fact-prof-l1* ""))
      (cons "FACT_PROF_L2" (if *nvk-fact-prof-l2* *nvk-fact-prof-l2* ""))
      (cons "FACT_PROF_L3" (if *nvk-fact-prof-l3* *nvk-fact-prof-l3* ""))
      (cons "FACT_PROF_L4" (if *nvk-fact-prof-l4* *nvk-fact-prof-l4* ""))
      (cons "FACT_PROF_L5" (if *nvk-fact-prof-l5* *nvk-fact-prof-l5* ""))
      (cons "PIPES"     (nvk-join hs ";"))
      (cons "SEG"       (if *nvk-seg-id* *nvk-seg-id* ""))))
  (princ "\n[НВК] состояние записано в чертёж.")
  T)

(defun nvk-nod-zagruzit ( / a v hs ss en had)
  (setq a (nvk-nod-chitat)  had a)
  (if a
    (progn
      (if (setq v (nvk-nod-get-any a '("BEDDING")))  (setq *nvk-bedding*   (atof v)))
      (if (setq v (nvk-nod-get-any a '("THK_ZASH" "THK_ZASHITA" "ZASHITA")))
        (setq *nvk-thk-zash*  (atof v)))
      (if (and (setq v (nvk-nod-get a "THK_ASPH")) (> (strlen v) 0))
        (setq *nvk-thk-asph* (atof v)))
      (if (and (setq v (nvk-nod-get a "THK_GAZN")) (> (strlen v) 0))
        (setq *nvk-thk-gazn* (atof v)))
      (if (and (setq v (nvk-nod-get a "THK_TROT")) (> (strlen v) 0))
        (setq *nvk-thk-trot* (atof v)))
      (if (and (setq v (nvk-nod-get a "THK_OTHER")) (> (strlen v) 0))
        (setq *nvk-thk-other* (atof v)))
      (if (and (setq v (nvk-nod-get a "FILL_ASPH")) (> (strlen v) 0))
        (setq *nvk-fill-asph* v))
      (if (and (setq v (nvk-nod-get a "FILL_TROT")) (> (strlen v) 0))
        (setq *nvk-fill-trot* v))
      (if (and (setq v (nvk-nod-get a "FILL_GAZN")) (> (strlen v) 0))
        (setq *nvk-fill-gazn* v))
      (if (and (setq v (nvk-nod-get a "FILL_OTHER")) (> (strlen v) 0))
        (setq *nvk-fill-other* v))
      (if (setq v (nvk-nod-get a "USE_BE"))
        (if (> (strlen v) 0) (setq *nvk-use-black-earth* (/= v "0"))))
      (if (setq v (nvk-nod-get a "BE_H")) (setq *nvk-black-earth-h* v))
      (if (setq v (nvk-nod-get a "BE_N")) (setq *nvk-black-earth-n* v))
      (if (setq v (nvk-nod-get a "L1_MH"))
        (if (> (strlen v) 0) (setq *nvk-l1-mh* (/= v "0"))))
      (if (and (setq v (nvk-nod-get a "TBL_OFF")) (> (strlen v) 0))
        (setq *nvk-table-off-m* (atof v)))
      (if (setq v (nvk-nod-get a "L1_PRESET"))
        (if (> (strlen v) 0) (setq *nvk-l1-preset* v)))
      (if (setq v (nvk-nod-get a "PAV_ALL"))
        (if (> (strlen v) 0) (setq *nvk-pav-all* (/= v "0"))))
      (if (setq v (nvk-nod-get a "ZONES"))
        (setq *nvk-zones-str* v))
      (if (setq v (nvk-nod-get a "USE_WALL"))
        (if (> (strlen v) 0) (setq *nvk-use-wall* (/= v "0"))))
      (if (and (setq v (nvk-nod-get a "WALLS")) (> (strlen v) 0))
        (setq *nvk-wall-str* v))
      (if (setq v (nvk-nod-get a "PROJ_FACT"))
        (if (> (strlen v) 0) (setq *nvk-proj-fact* (/= v "0"))))
      (if (setq v (nvk-nod-get a "SINGLE_SC"))
        (if (> (strlen v) 0) (setq *nvk-single-scatter* (/= v "0"))))
      (if (setq v (nvk-nod-get a "USE_SC_R"))
        (if (> (strlen v) 0) (setq *nvk-use-sc-r* (/= v "0"))))
      (if (setq v (nvk-nod-get a "USE_SC_T"))
        (if (> (strlen v) 0) (setq *nvk-use-sc-t* (/= v "0"))))
      (if (setq v (nvk-nod-get a "USE_SC_Z"))
        (if (> (strlen v) 0) (setq *nvk-use-sc-z* (/= v "0"))))
      (if (setq v (nvk-nod-get a "USE_SC_S"))
        (if (> (strlen v) 0) (setq *nvk-use-sc-s* (/= v "0"))))
      (if (and (setq v (nvk-nod-get a "SC_R")) (> (strlen v) 0)) (setq *nvk-sc-r* (atof v)))
      (if (and (setq v (nvk-nod-get a "SC_T")) (> (strlen v) 0)) (setq *nvk-sc-t* (atof v)))
      (if (and (setq v (nvk-nod-get a "SC_Z")) (> (strlen v) 0)) (setq *nvk-sc-z* (atof v)))
      (if (and (setq v (nvk-nod-get a "SC_S")) (> (strlen v) 0)) (setq *nvk-sc-s* (atof v)))
      (if (setq v (nvk-nod-get a "ANNOT"))
        (if (> (strlen v) 0) (setq *nvk-annotative* (/= v "0"))))
      (if (and (setq v (nvk-nod-get a "ANN_GAP")) (> (strlen v) 0)) (setq *nvk-ann-gap* (atof v)))
      (if (setq v (nvk-nod-get a "PLAN_EN"))
        (if (> (strlen v) 0) (setq *nvk-plan-en* (/= v "0"))))
      (if (and (setq v (nvk-nod-get a "PLAN_INT")) (> (strlen v) 0)) (setq *nvk-plan-int* (atof v)))
      (if (and (setq v (nvk-nod-get a "PLAN_MIN")) (> (strlen v) 0)) (setq *nvk-plan-min* (atof v)))
      (if (setq v (nvk-nod-get a "DRAW_PROJ"))
        (if (> (strlen v) 0) (setq *nvk-draw-proj* (/= v "0"))))
      (if (setq v (nvk-nod-get a "DELTA_H"))
        (if (> (strlen v) 0) (setq *nvk-delta-h* (/= v "0"))))
      (if (setq v (nvk-nod-get a "SCATTER")) (setq *nvk-scatter-vals* v))
      (if (setq v (nvk-nod-get a "SCATTER2")) (setq *nvk-scatter-l2* v))
      (if (setq v (nvk-nod-get a "SCATTER3")) (setq *nvk-scatter-l3* v))
      (if (setq v (nvk-nod-get a "SCATTER4")) (setq *nvk-scatter-l4* v))
      (if (setq v (nvk-nod-get a "SCATTER5")) (setq *nvk-scatter-l5* v))
      (if (setq v (nvk-nod-get a "LATOFF")) (setq *nvk-latoff-vals* v))
      (if (setq v (nvk-nod-get a "PLAN_TGT")) (setq *nvk-plan-tgt* v))
      (if (setq v (nvk-nod-get a "PLAN_LAT")) (setq *nvk-plan-lat* v))
      (if (and (setq v (nvk-nod-get-any a '("CS_YGAP" "YGAP"))) (> (strlen v) 0))
        (setq *nvk-cs-ygap* (atof v)))
      (if (and (setq v (nvk-nod-get a "CS_COLS")) (> (strlen v) 0))
        (setq *nvk-cs-cols* (atoi v)))
      (if (setq v (nvk-nod-get a "JOINT"))
        (if (> (strlen v) 0) (setq *nvk-joint* v)))
      (if (setq v (nvk-nod-get-any a '("CS_SLOPE" "SLOPE" "M_SLOPE")))
        (setq *nvk-cs-slope*  (atof v)))
      (if (setq v (nvk-nod-get-any a '("CS_SCALE"))) (setq *nvk-cs-scale*  (atof v)))
      (if (setq v (nvk-nod-get-any a '("H_SCALE" "HSCALE")))  (setq *nvk-h-scale*   (atof v)))
      (if (setq v (nvk-nod-get-any a '("L_SCALE" "LSCALE")))  (setq *nvk-l-scale*   (atof v)))
      (if (setq v (nvk-nod-get a "STATIONS"))
        (if (> (strlen v) 0) (setq *nvk-stations-str* v)))
      (if (setq v (nvk-nod-get a "BLOCK_CS"))
        (if (> (strlen v) 0) (setq *nvk-block-cs* (/= v "0"))))
      (if (setq v (nvk-nod-get a "BLOCK_EP"))
        (if (> (strlen v) 0) (setq *nvk-block-ep* (/= v "0"))))
      (if (setq v (nvk-nod-get a "SHOW_TAGS"))
        (if (> (strlen v) 0) (setq *nvk-show-tags* (/= v "0"))))
      (if (and (setq v (nvk-nod-get a "HWIDTH")) (> (strlen v) 0))
        (setq *nvk-cs-hwidth* (atof v)))
      (if (and (setq v (nvk-nod-get-any a '("TEXT_H" "TEXT_HEIGHT"))) (> (strlen v) 0))
        (setq *nvk-text-h* (atof v)))
      (if (and (setq v (nvk-nod-get-any a '("CS_TH" "CS_TEXT_H" "CS_TEXT"))) (> (strlen v) 0))
        (setq *nvk-cs-text-h* (atof v)))
      (if (and (setq v (nvk-nod-get a "TEXT_OFF")) (> (strlen v) 0))
        (setq *nvk-text-off* (atof v)))
      (if (and (setq v (nvk-nod-get a "ROUND_TO")) (> (strlen v) 0))
        (setq *nvk-round-to* (atoi v)))
      (if (and (setq v (nvk-nod-get a "SLOPE_RND")) (> (strlen v) 0))
        (setq *nvk-slope-round* (atoi v)))
      (if (and (setq v (nvk-nod-get a "SLOPE_U")) (> (strlen v) 0))
        (setq *nvk-slope-unit* v))
      (if (setq v (nvk-nod-get a "SHOW_PERM"))
        (if (> (strlen v) 0) (setq *nvk-show-permille* (/= v "0"))))
      (if (setq v (nvk-nod-get a "SHOW_LEN"))
        (if (> (strlen v) 0) (setq *nvk-show-len* (/= v "0"))))
      (if (setq v (nvk-nod-get a "SHOW_SLP"))
        (if (> (strlen v) 0) (setq *nvk-show-slope* (/= v "0"))))
      (if (and (setq v (nvk-nod-get a "LAB_W")) (> (strlen v) 0))
        (setq *nvk-label-col-w* (atof v)))
      (setq *nvk-surf-handle* (nvk-nod-get a "SURF_H")
            *nvk-surf-name*   (nvk-nod-get a "SURF_N"))
      (if (and *nvk-surf-handle* (= *nvk-surf-handle* "")) (setq *nvk-surf-handle* nil))
      (if (and *nvk-surf-name* (= *nvk-surf-name* "")) (setq *nvk-surf-name* nil))
      (setq v (nvk-nod-get a "CS_X"))
      (if (and v (> (strlen v) 0) (nvk-nod-get a "CS_Y") (> (strlen (nvk-nod-get a "CS_Y")) 0))
        (setq *nvk-cs-ins* (list (atof v) (atof (nvk-nod-get a "CS_Y")))))
      (setq v (nvk-nod-get a "EP_X"))
      (if (and v (> (strlen v) 0) (nvk-nod-get a "EP_Y") (> (strlen (nvk-nod-get a "EP_Y")) 0))
        (setq *nvk-ep-ins* (list (atof v) (atof (nvk-nod-get a "EP_Y")))))
      (setq v (nvk-nod-get a "VOL_X"))
      (if (and v (> (strlen v) 0) (nvk-nod-get a "VOL_Y") (> (strlen (nvk-nod-get a "VOL_Y")) 0))
        (setq *nvk-vol-ins* (list (atof v) (atof (nvk-nod-get a "VOL_Y")))))
      (setq hs (nvk-nod-get a "PIPES")  ss nil)
      (if (and hs (> (strlen hs) 0))
        (foreach h (nvk-split hs ";")
          (setq en (handent h))
          (if en
            (setq ss (if ss (progn (ssadd en ss) ss) (ssadd en))))))
      (if ss (setq *nvk-pipe-ss* ss))
      (if (setq v (nvk-nod-get a "EP_LVLS"))
        (setq *nvk-ep-lpts* (nvk-lpts-parse v)))
      (if (setq v (nvk-nod-get a "CS_LVLS"))
        (setq *nvk-cs-lpts* (nvk-lpts-parse v)))
      (if (setq v (nvk-nod-get a "TBL_ROWS_L1")) (setq *nvk-rows-l1* v))
      (if (setq v (nvk-nod-get a "TBL_ROWS_L2")) (setq *nvk-rows-l2* v))
      (if (setq v (nvk-nod-get a "TBL_ROWS_L3")) (setq *nvk-rows-l3* v))
      (if (setq v (nvk-nod-get a "TBL_ROWS_L4")) (setq *nvk-rows-l4* v))
      (if (setq v (nvk-nod-get a "TBL_ROWS_L5")) (setq *nvk-rows-l5* v))
      (if (setq v (nvk-nod-get a "FACT_PROF_L1")) (setq *nvk-fact-prof-l1* v))
      (if (setq v (nvk-nod-get a "FACT_PROF_L2")) (setq *nvk-fact-prof-l2* v))
      (if (setq v (nvk-nod-get a "FACT_PROF_L3")) (setq *nvk-fact-prof-l3* v))
      (if (setq v (nvk-nod-get a "FACT_PROF_L4")) (setq *nvk-fact-prof-l4* v))
      (if (setq v (nvk-nod-get a "FACT_PROF_L5")) (setq *nvk-fact-prof-l5* v))
      (princ (strcat "\n[НВК] из чертежа: труб "
                     (if (and *nvk-pipe-ss* (> (sslength *nvk-pipe-ss*) 0))
                       (itoa (sslength *nvk-pipe-ss*)) "0")
                     "  TIN=" (if *nvk-surf-name* *nvk-surf-name* "-")
                     "  покрытия="
                     (if (and *nvk-zones-str* (> (strlen *nvk-zones-str*) 0))
                       *nvk-zones-str* "(нет)")))
      T))
  (vl-catch-all-apply 'nvk-nod-import-pb (list had))
  (if (or had *nvk-pipe-ss* *nvk-cs-ins* *nvk-ep-ins*) T nil))

(if (not (boundp '*nvk-doc-key*)) (setq *nvk-doc-key* nil))

(defun nvk-doc-key ( )
  (strcat (if (getvar "DWGPREFIX") (getvar "DWGPREFIX") "")
          (if (getvar "DWGNAME") (getvar "DWGNAME") "")))

;; BecameCurrent срабатывает и на Обновить/команды — не трогаем зоны того же DWG.
(defun nvk-on-doc (rea cmd / k)
  (setq k (nvk-doc-key))
  (if (and k (> (strlen k) 0) (not (equal k *nvk-doc-key*)))
    (progn
      (setq *nvk-doc-key* k)
      (vl-catch-all-apply 'nvk-nod-zagruzit nil)
      (if (and (boundp 'nvk-ui-otdat) (car (atoms-family 1 '("NVK-UI-PUT"))))
        (vl-catch-all-apply 'nvk-ui-otdat nil)))))

(defun nvk-doc-reactor ( / )
  (if (and (boundp '*nvk-doc-reac*) *nvk-doc-reac*)
    (vl-catch-all-apply 'vlr-remove (list *nvk-doc-reac*)))
  (setq *nvk-doc-reac*
        (vlr-docmanager-reactor
          nil
          (list
            (cons :vlr-documentBecameCurrent 'nvk-on-doc)
            (cons :vlr-documentCreated 'nvk-on-doc)))))

(vl-catch-all-apply 'nvk-doc-reactor nil)

(princ "\n  nvk-nod.lsp")
(princ)
