;;; nvk-commands.lsp — пользовательские команды
;;; Зависит от: все nvk-*.

(defun C:НВК-ИНФО ( / dll-s)
  (nvk-dll-zagruzit)
  (setq dll-s (vl-catch-all-apply 'nvk-dll-ping-stroka nil))
  (if (vl-catch-all-error-p dll-s) (setq dll-s (vl-catch-all-error-message dll-s)))
  (princ "\n")
  (princ "╔══════════════════════════════════════════════╗")
  (princ (strcat "\n║  Поперечник НВК  " *nvk-versija*))
  (princ "\n╠══════════════════════════════════════════════╣")
  (princ (strcat "\n║  папка  " *nvk-dir*))
  (princ (strcat "\n║  DLL    " (if *nvk-dll-ok* "да" "нет")
                 "  " (if dll-s dll-s "?")))
  (princ (strcat "\n║  блоки  CS=" (if *nvk-block-cs* "да" "нет")
                 "  EP=" (if *nvk-block-ep* "да" "нет")
                 "  POPER=" (if *nvk-block-poper* "да" "нет")
                 "  TIN±" (rtos *nvk-cs-hwidth* 2 1) "м"))
  (princ (strcat "\n║  труб   " (if (and *nvk-pipe-ss* (> (sslength *nvk-pipe-ss*) 0))
                      (itoa (sslength *nvk-pipe-ss*)) "нет")
                 "  TIN=" (if *nvk-surf-name* *nvk-surf-name* "-")))
  (princ (strcat "\n║  CS pt  " (nvk-pt-str *nvk-cs-ins*)
                 "  EP pt " (nvk-pt-str *nvk-ep-ins*)))
  (princ "\n╠══════════════════════════════════════════════╣")
  (princ "\n║  два исходника: труба + TIN                  ║")
  (princ "\n║  TrenchBottom → низ разработки и низ песка   ║")
  (princ "\n║  SandTop      → низ защиты (верх песка)      ║")
  (princ "\n║  ZashTop      → низ засыпки                  ║")
  (princ "\n╠══════════════════════════════════════════════╣")
  (princ "\n║  НВК-ПОСТРОИТЬ  все этапы, лог OK/SKIP/FAIL  ║")
  (princ "\n║  НВК-ВВОД       трубы + TIN                  ║")
  (princ (strcat "\n║  лог    " *nvk-dir* "\\nvk-log.txt"))
  (princ "\n║  НВК-ДАМП       домен в nvk-log.txt          ║")
  (princ "\n║  НВК-СЕЧЕНИЯ    поперечники (блок/россыпь)   ║")
  (princ "\n║  НВК-ПРОФИЛЬ    продольники (блок/россыпь)   ║")
  (princ "\n║  НВК-ПОДПИСИ    таблица отметок/уклонов      ║")
  (princ "\n║  НВК-ОБЪЁМЫ     объёмы из домена             ║")
  (princ "\n║  НВК-ПЛАН       ось и траншея в плане        ║")
  (princ "\n║  НВК-ПАНЕЛЬ     панель DLL (всё управление)   ║")
  (princ "\n║  НВК-ДВИГАТЬ    сдвинуть профиль или сечение  ║")
  (princ "\n║  НВК-НАСТРОЙКИ  DCL (запасной диалог)         ║")
  (princ "\n║  НВК-ОБНОВИТЬ   пересчёт, точки те же        ║")
  (princ "\n║  НВК-ОЧИСТИТЬ   только графика NVK-*         ║")
  (princ "\n║  НВК-СБРОС      забыть точки вставки         ║")
  (princ "\n║  НВК-СЛОИ / НВК-ИНФО                         ║")
  (princ "\n╚══════════════════════════════════════════════╝")
  (princ)
  (princ))

(defun nvk-pt-str (p)
  (if (and p (listp p) (>= (length p) 2))
    (strcat (rtos (car p) 2 1) "," (rtos (cadr p) 2 1))
    "-"))

(defun C:НВК-НАСТРОЙКИ ( / )
  (nvk-dialog-nastrojki)
  (princ))

(defun nvk-plist-get (lst key)
  (cond
    ((null lst) nil)
    ((equal (strcase (car lst)) (strcase key)) (cadr lst))
    (t (nvk-plist-get (cddr lst) key))))

(defun nvk-ui-01 (s) (and s (/= s "0") (/= s "")))

;; Палитра modeless: SendStringToExecute «(nvk-ui-primenit)» кладёт имя на
;; командный стек; на unlock Civil ищет C:NVK-UI-PRIMENIT и орёт
;; «no function definition». Все вызовы с панели — через C: ниже.
(defun C:NVK-UI-PRIMENIT ( / )
  (nvk-ui-primenit)
  (princ))

(defun C:НВК-ПАНЕЛЬ-ПРОГОН ( / )
  (nvk-ui-primenit)
  (C:НВК-ПОСТРОИТЬ)
  (princ))

(defun C:НВК-ПАНЕЛЬ-ДАМП ( / )
  (nvk-ui-primenit)
  (C:НВК-ДАМП)
  (princ))

(defun C:НВК-ПАНЕЛЬ-ОЧИСТИТЬ ( / )
  (nvk-ui-primenit)
  (C:НВК-ОЧИСТИТЬ)
  (princ))

(defun C:НВК-ПАНЕЛЬ-РАНДОМ ( / )
  (nvk-ui-primenit)
  (C:НВК-РАНДОМ)
  (princ))

(defun nvk-ui-primenit ( / a v)
  (setq a (vl-catch-all-apply 'nvk-ui-get nil))
  (if (or (null a) (vl-catch-all-error-p a) (not (listp a)))
    nil
    (progn
      (if (setq v (nvk-plist-get a "BEDDING"))  (setq *nvk-bedding*   (atof v)))
      (if (setq v (nvk-plist-get a "THK_ZASH")) (setq *nvk-thk-zash*  (atof v)))
      (if (setq v (nvk-plist-get a "THK_ASPH")) (setq *nvk-thk-asph*  (atof v)))
      (if (setq v (nvk-plist-get a "THK_GAZN")) (setq *nvk-thk-gazn*  (atof v)))
      (if (setq v (nvk-plist-get a "THK_TROT")) (setq *nvk-thk-trot*  (atof v)))
      (if (setq v (nvk-plist-get a "THK_OTHER")) (setq *nvk-thk-other* (atof v)))
      (if (setq v (nvk-plist-get a "FILL_ASPH")) (setq *nvk-fill-asph* v))
      (if (setq v (nvk-plist-get a "FILL_TROT")) (setq *nvk-fill-trot* v))
      (if (setq v (nvk-plist-get a "FILL_GAZN")) (setq *nvk-fill-gazn* v))
      (if (setq v (nvk-plist-get a "FILL_OTHER")) (setq *nvk-fill-other* v))
      (if (setq v (nvk-plist-get a "USE_BE")) (setq *nvk-use-black-earth* (nvk-ui-01 v)))
      (if (setq v (nvk-plist-get a "BE_H")) (setq *nvk-black-earth-h* v))
      (if (setq v (nvk-plist-get a "BE_N")) (setq *nvk-black-earth-n* v))
      (if (setq v (nvk-plist-get a "DESIGN_H"))
        (if (and v (> (strlen v) 0))
          (setq *nvk-surf-handle* v)))
      (if (setq v (nvk-plist-get a "DESIGN_N"))
        (if (and v (> (strlen v) 0))
          (setq *nvk-surf-name* v)))
      (if (setq v (nvk-plist-get a "L1_MH")) (setq *nvk-l1-mh* (nvk-ui-01 v)))
      (if (setq v (nvk-plist-get a "TBL_OFF")) (setq *nvk-table-off-m* (atof v)))
      (if (setq v (nvk-plist-get a "L1_PRESET")) (setq *nvk-l1-preset* v))
      (if (setq v (nvk-plist-get a "CS_YGAP"))  (setq *nvk-cs-ygap*   (atof v)))
      (if (setq v (nvk-plist-get a "CS_COLS"))  (setq *nvk-cs-cols*   (atoi v)))
      (if (setq v (nvk-plist-get a "JOINT"))
        (if (> (strlen v) 0) (setq *nvk-joint* v)))
      (if (setq v (nvk-plist-get a "SLOPE"))    (setq *nvk-cs-slope*  (atof v)))
      (if (setq v (nvk-plist-get a "HWIDTH"))   (setq *nvk-cs-hwidth* (atof v)))
      (if (setq v (nvk-plist-get a "H_SCALE"))  (setq *nvk-h-scale*   (atof v)))
      (if (setq v (nvk-plist-get a "L_SCALE"))  (setq *nvk-l-scale*   (atof v)))
      (if (setq v (nvk-plist-get a "CS_SCALE")) (setq *nvk-cs-scale*  (atof v)))
      (if (setq v (nvk-plist-get a "CS_TH"))    (setq *nvk-cs-text-h* (atof v)))
      (if (setq v (nvk-plist-get a "TEXT_H"))   (setq *nvk-text-h*    (atof v)))
      (if (setq v (nvk-plist-get a "TEXT_OFF")) (setq *nvk-text-off*  (atof v)))
      (if (setq v (nvk-plist-get a "ROUND_TO")) (setq *nvk-round-to*  (atoi v)))
      (if (setq v (nvk-plist-get a "SLOPE_RND"))(setq *nvk-slope-round* (atoi v)))
      (if (setq v (nvk-plist-get a "SLOPE_U"))
        (if (> (strlen v) 0) (setq *nvk-slope-unit* v)))
      (if (setq v (nvk-plist-get a "SHOW_PERM")) (setq *nvk-show-permille* (nvk-ui-01 v)))
      (if (setq v (nvk-plist-get a "SHOW_LEN"))  (setq *nvk-show-len* (nvk-ui-01 v)))
      (if (setq v (nvk-plist-get a "SHOW_SLP"))  (setq *nvk-show-slope* (nvk-ui-01 v)))
      (if (setq v (nvk-plist-get a "LAB_W"))     (setq *nvk-label-col-w* (atof v)))
      (if (setq v (nvk-plist-get a "BLOCK_CS"))  (setq *nvk-block-cs* (nvk-ui-01 v)))
      (if (setq v (nvk-plist-get a "BLOCK_EP"))  (setq *nvk-block-ep* (nvk-ui-01 v)))
      (if (setq v (nvk-plist-get a "SHOW_TAGS")) (setq *nvk-show-tags* (nvk-ui-01 v)))
      (if (setq v (nvk-plist-get a "STATIONS"))
        (if (> (strlen v) 0) (setq *nvk-stations-str* v)))
      (if (setq v (nvk-plist-get a "DO_CS"))    (setq *nvk-do-cs*    (nvk-ui-01 v)))
      (if (setq v (nvk-plist-get a "DO_EP"))    (setq *nvk-do-ep*    (nvk-ui-01 v)))
      (if (setq v (nvk-plist-get a "DO_POPER")) (setq *nvk-do-poper* (nvk-ui-01 v)))
      (if (setq v (nvk-plist-get a "DO_VOL"))   (setq *nvk-do-vol*   (nvk-ui-01 v)))
      (if (setq v (nvk-plist-get a "DO_PLAN"))  (setq *nvk-do-plan*  (nvk-ui-01 v)))
      (if (setq v (nvk-plist-get a "PROJ_FACT")) (setq *nvk-proj-fact* (nvk-ui-01 v)))
      (if (setq v (nvk-plist-get a "SINGLE_SC")) (setq *nvk-single-scatter* (nvk-ui-01 v)))
      (if (setq v (nvk-plist-get a "USE_SC_R")) (setq *nvk-use-sc-r* (nvk-ui-01 v)))
      (if (setq v (nvk-plist-get a "USE_SC_T")) (setq *nvk-use-sc-t* (nvk-ui-01 v)))
      (if (setq v (nvk-plist-get a "USE_SC_Z")) (setq *nvk-use-sc-z* (nvk-ui-01 v)))
      (if (setq v (nvk-plist-get a "USE_SC_S")) (setq *nvk-use-sc-s* (nvk-ui-01 v)))
      (if (setq v (nvk-plist-get a "SC_R")) (setq *nvk-sc-r* (atof v)))
      (if (setq v (nvk-plist-get a "SC_T")) (setq *nvk-sc-t* (atof v)))
      (if (setq v (nvk-plist-get a "SC_Z")) (setq *nvk-sc-z* (atof v)))
      (if (setq v (nvk-plist-get a "SC_S")) (setq *nvk-sc-s* (atof v)))
      (if (setq v (nvk-plist-get a "ANNOT")) (setq *nvk-annotative* (nvk-ui-01 v)))
      (if (setq v (nvk-plist-get a "ANN_GAP")) (setq *nvk-ann-gap* (atof v)))
      (if (setq v (nvk-plist-get a "PAV_ALL")) (setq *nvk-pav-all* (nvk-ui-01 v)))
      (if (setq v (nvk-plist-get a "PICK_ZONES")) (setq *nvk-pick-zones* (nvk-ui-01 v)))
      (if (setq v (nvk-plist-get a "ZONES"))
        (if (or (> (strlen v) 0)
                (not *nvk-zones-str*)
                (= *nvk-zones-str* ""))
          (setq *nvk-zones-str* v)))
      (if (setq v (nvk-plist-get a "USE_WALL")) (setq *nvk-use-wall* (nvk-ui-01 v)))
      (if (setq v (nvk-plist-get a "WALLS"))
        (if (> (strlen v) 0) (setq *nvk-wall-str* v)))
      (if (setq v (nvk-plist-get a "PLAN_EN")) (setq *nvk-plan-en* (nvk-ui-01 v)))
      (if (setq v (nvk-plist-get a "PLAN_INT")) (setq *nvk-plan-int* (atof v)))
      (if (setq v (nvk-plist-get a "PLAN_MIN")) (setq *nvk-plan-min* (atof v)))
      (if (setq v (nvk-plist-get a "DRAW_PROJ")) (setq *nvk-draw-proj* (nvk-ui-01 v)))
      (if (setq v (nvk-plist-get a "USE_TH")) (setq *nvk-use-th* (nvk-ui-01 v)))
      (if (setq v (nvk-plist-get a "DELTA_H")) (setq *nvk-delta-h* (nvk-ui-01 v)))
      (if (setq v (nvk-plist-get a "LAB_H")) (setq *nvk-lab-h* v))
      (if (setq v (nvk-plist-get a "LAB_L")) (setq *nvk-lab-l* v))
      (if (setq v (nvk-plist-get a "LAB_S")) (setq *nvk-lab-s* v))
      (if (setq v (nvk-plist-get a "TBL_ROWS_L1")) (setq *nvk-rows-l1* v))
      (if (setq v (nvk-plist-get a "TBL_ROWS_L2")) (setq *nvk-rows-l2* v))
      (if (setq v (nvk-plist-get a "TBL_ROWS_L3")) (setq *nvk-rows-l3* v))
      (if (setq v (nvk-plist-get a "TBL_ROWS_L4")) (setq *nvk-rows-l4* v))
      (if (setq v (nvk-plist-get a "TBL_ROWS_L5")) (setq *nvk-rows-l5* v))
      (if (setq v (nvk-plist-get a "FACT_PROF_L1")) (setq *nvk-fact-prof-l1* v))
      (if (setq v (nvk-plist-get a "FACT_PROF_L2")) (setq *nvk-fact-prof-l2* v))
      (if (setq v (nvk-plist-get a "FACT_PROF_L3")) (setq *nvk-fact-prof-l3* v))
      (if (setq v (nvk-plist-get a "FACT_PROF_L4")) (setq *nvk-fact-prof-l4* v))
      (if (setq v (nvk-plist-get a "FACT_PROF_L5")) (setq *nvk-fact-prof-l5* v))
      (nvk-table-apply)
      (vl-catch-all-apply 'nvk-nod-sohranit nil)
      T)))

;; AutoLISP: не больше 128 аргументов. NVK-UI-PUT пачками, иначе otdat молча падает
;; и панель/домен остаются без ZONES после открытия чертежа.
(defun nvk-ui-put-pairs (lst / chunk n)
  (if (not (car (atoms-family 1 '("NVK-UI-PUT"))))
    nil
    (progn
      (while lst
        (setq chunk nil n 0)
        (while (and lst (< n 80))
          (setq chunk (append chunk (list (car lst)))
                lst (cdr lst)
                n (1+ n)))
        (if chunk (vl-catch-all-apply 'nvk-ui-put chunk)))
      T)))

(defun nvk-ui-otdat ( / )
  (nvk-ui-put-pairs
    (list
      "BEDDING"   (rtos *nvk-bedding* 2 4)
      "THK_ZASH"  (rtos *nvk-thk-zash* 2 4)
      "THK_ASPH"  (rtos *nvk-thk-asph* 2 4)
      "THK_GAZN"  (rtos (if *nvk-thk-gazn* *nvk-thk-gazn* 0.0) 2 4)
      "THK_TROT"  (rtos (if *nvk-thk-trot* *nvk-thk-trot* 0.0) 2 4)
      "THK_OTHER" (rtos (if *nvk-thk-other* *nvk-thk-other* 0.35) 2 4)
      "FILL_ASPH"  (if *nvk-fill-asph* *nvk-fill-asph* "SAND")
      "FILL_TROT"  (if *nvk-fill-trot* *nvk-fill-trot* "SAND")
      "FILL_GAZN"  (if *nvk-fill-gazn* *nvk-fill-gazn* "SOIL")
      "FILL_OTHER" (if *nvk-fill-other* *nvk-fill-other* "SOIL")
      "USE_BE"    (if *nvk-use-black-earth* "1" "0")
      "BE_H"      (if *nvk-black-earth-h* *nvk-black-earth-h* "")
      "BE_N"      (if *nvk-black-earth-n* *nvk-black-earth-n* "")
      "DESIGN_H"  (if *nvk-surf-handle* *nvk-surf-handle* "")
      "DESIGN_N"  (if *nvk-surf-name* *nvk-surf-name* "")
      "L1_MH"     (if *nvk-l1-mh* "1" "0")
      "TBL_OFF"   (rtos (if *nvk-table-off-m* *nvk-table-off-m* 1.0) 2 2)
      "L1_PRESET" (if *nvk-l1-preset* *nvk-l1-preset* "default")
      "CS_YGAP"   (rtos (if *nvk-cs-ygap* *nvk-cs-ygap* 100.0) 2 1)
      "CS_COLS"   (itoa (if *nvk-cs-cols* *nvk-cs-cols* 2))
      "JOINT"     (if *nvk-joint* *nvk-joint* "SOCKET")
      "SLOPE"     (rtos *nvk-cs-slope* 2 4)
      "HWIDTH"    (rtos *nvk-cs-hwidth* 2 3)
      "H_SCALE"   (rtos *nvk-h-scale* 2 2)
      "L_SCALE"   (rtos *nvk-l-scale* 2 2)
      "CS_SCALE"  (rtos *nvk-cs-scale* 2 2)
      "CS_TH"     (rtos *nvk-cs-text-h* 2 3)
      "TEXT_H"    (rtos *nvk-text-h* 2 3)
      "TEXT_OFF"  (rtos *nvk-text-off* 2 1)
      "ROUND_TO"  (itoa (if *nvk-round-to* *nvk-round-to* 2))
      "SLOPE_RND" (itoa (if *nvk-slope-round* *nvk-slope-round* 1))
      "SLOPE_U"   (if *nvk-slope-unit* *nvk-slope-unit* "permille")
      "SHOW_PERM" (if *nvk-show-permille* "1" "0")
      "SHOW_LEN"  (if *nvk-show-len* "1" "0")
      "SHOW_SLP"  (if *nvk-show-slope* "1" "0")
      "LAB_W"     (rtos *nvk-label-col-w* 2 2)
      "BLOCK_CS"  (if *nvk-block-cs* "1" "0")
      "BLOCK_EP"  (if *nvk-block-ep* "1" "0")
      "SHOW_TAGS" (if *nvk-show-tags* "1" "0")
      "STATIONS"  (if *nvk-stations-str* *nvk-stations-str* "AUTO")
      "DO_CS"     (if *nvk-do-cs* "1" "0")
      "DO_EP"     (if *nvk-do-ep* "1" "0")
      "DO_POPER"  (if *nvk-do-poper* "1" "0")
      "DO_VOL"    (if *nvk-do-vol* "1" "0")
      "DO_PLAN"   (if *nvk-do-plan* "1" "0")
      "PROJ_FACT" (if *nvk-proj-fact* "1" "0")
      "SINGLE_SC" (if *nvk-single-scatter* "1" "0")
      "USE_SC_R"  (if *nvk-use-sc-r* "1" "0")
      "USE_SC_T"  (if *nvk-use-sc-t* "1" "0")
      "USE_SC_Z"  (if *nvk-use-sc-z* "1" "0")
      "USE_SC_S"  (if *nvk-use-sc-s* "1" "0")
      "SC_R"      (rtos (if *nvk-sc-r* *nvk-sc-r* 0.05) 2 4)
      "SC_T"      (rtos (if *nvk-sc-t* *nvk-sc-t* 0.005) 2 4)
      "SC_Z"      (rtos (if *nvk-sc-z* *nvk-sc-z* 0.05) 2 4)
      "SC_S"      (rtos (if *nvk-sc-s* *nvk-sc-s* 0.05) 2 4)
      "ANNOT"     (if *nvk-annotative* "1" "0")
      "ANN_GAP"   (rtos (if *nvk-ann-gap* *nvk-ann-gap* 10.0) 2 1)
      "PAV_ALL"   (if *nvk-pav-all* "1" "0")
      "PICK_ZONES"(if *nvk-pick-zones* "1" "0")
      "ZONES"     (if *nvk-zones-str* *nvk-zones-str* "")
      "USE_WALL"  (if *nvk-use-wall* "1" "0")
      "WALLS"     (if *nvk-wall-str* *nvk-wall-str* "")
      "PLAN_EN"   (if *nvk-plan-en* "1" "0")
      "PLAN_INT"  (rtos (if *nvk-plan-int* *nvk-plan-int* 50.0) 2 1)
      "PLAN_MIN"  (rtos (if *nvk-plan-min* *nvk-plan-min* 15.0) 2 1)
      "DRAW_PROJ" (if *nvk-draw-proj* "1" "0")
      "USE_TH"    (if *nvk-use-th* "1" "0")
      "DELTA_H"   (if *nvk-delta-h* "1" "0")
      "LAB_H"     (if *nvk-lab-h* *nvk-lab-h* "")
      "LAB_L"     (if *nvk-lab-l* *nvk-lab-l* "")
      "LAB_S"     (if *nvk-lab-s* *nvk-lab-s* "")
      "TBL_ROWS_L1" (if *nvk-rows-l1* *nvk-rows-l1* "")
      "TBL_ROWS_L2" (if *nvk-rows-l2* *nvk-rows-l2* "")
      "TBL_ROWS_L3" (if *nvk-rows-l3* *nvk-rows-l3* "")
      "TBL_ROWS_L4" (if *nvk-rows-l4* *nvk-rows-l4* "")
      "TBL_ROWS_L5" (if *nvk-rows-l5* *nvk-rows-l5* "")
      "FACT_PROF_L1" (if *nvk-fact-prof-l1* *nvk-fact-prof-l1* "")
      "FACT_PROF_L2" (if *nvk-fact-prof-l2* *nvk-fact-prof-l2* "")
      "FACT_PROF_L3" (if *nvk-fact-prof-l3* *nvk-fact-prof-l3* "")
      "FACT_PROF_L4" (if *nvk-fact-prof-l4* *nvk-fact-prof-l4* "")
      "FACT_PROF_L5" (if *nvk-fact-prof-l5* *nvk-fact-prof-l5* ""))))

(defun C:НВК-ПАНЕЛЬ ( / )
  (if (not (nvk-dll-zagruzit))
    (princ "\n[НВК] без DLL панель не открыть.")
    (if (null (car (atoms-family 1 '("NVK-UI"))))
      (princ "\n[НВК] старая DLL в памяти. Полностью закрой Civil и load снова.")
      (progn
        (vl-catch-all-apply 'nvk-nod-zagruzit nil)
        (nvk-ui-otdat)
        (vl-catch-all-apply 'nvk-ui nil)
        (princ "\n[НВК] панель слева. Построить — кнопкой."))))
  (princ))

(defun C:NVKPANEL () (C:НВК-ПАНЕЛЬ))

(defun C:НВК-СТРОКИ ( / )
  (if (not (nvk-dll-zagruzit))
    (princ "\n[НВК] без DLL панель не открыть.")
    (if (null (car (atoms-family 1 '("NVK-ROWS-PANEL"))))
      (progn
        (C:НВК-ПАНЕЛЬ)
        (princ "\n[НВК] обнови DLL для панели строк."))
      (progn
        (vl-catch-all-apply 'nvk-nod-zagruzit nil)
        (nvk-ui-otdat)
        (vl-catch-all-apply 'nvk-rows-panel nil)
        (princ "\n[НВК] панель строк таблицы открыта."))))
  (princ))

(defun C:НВК-СЛОИ ( / )
  (nvk-registr-appid)
  (nvk-sozdat-vse-sloi)
  (princ "\n[НВК] слои NVK-* и AppID готовы.")
  (princ))



(defun C:НВК-ВВОД ( / )
  (setq *nvk-input-sprosit* T)
  (nvk-stage-input)
  (setq *nvk-input-sprosit* nil)
  (princ))

(defun C:НВК-ДАМП ( / )
  (if (not (nvk-dll-zagruzit))
    (princ "\n[НВК] без DLL дамп не посчитать.")
    (progn
      (if (null *nvk-pipe-ss*)
        (nvk-stage-input))
      (nvk-stage-domain)))
  (princ))

(defun C:НВК-СЕЧЕНИЯ ( / )
  (if (not (nvk-dll-zagruzit))
    (princ "\n[НВК] без DLL.")
    (progn
      (if (null *nvk-pipe-ss*)
        (nvk-stage-input))
      (nvk-stage-domain)
      (nvk-stage-cs-draw)))
  (princ))

(defun C:НВК-ПРОФИЛЬ ( / )
  (if (not (nvk-dll-zagruzit))
    (princ "\n[НВК] без DLL.")
    (progn
      (if (null *nvk-pipe-ss*)
        (nvk-stage-input))
      (nvk-stage-domain)
      (nvk-stage-ep)))
  (princ))

(defun C:НВК-ПОДПИСИ ( / )
  (if (not (nvk-dll-zagruzit))
    (princ "\n[НВК] без DLL.")
    (progn
      (if (null *nvk-ep-ins*)
        (nvk-stage-ep))
      (nvk-stage-poper)))
  (princ))

(defun C:НВК-ОБЪЁМЫ ( / )
  (if (not (nvk-dll-zagruzit))
    (princ "\n[НВК] без DLL.")
    (progn
      (if (null *nvk-pipe-ss*) (nvk-stage-input))
      (nvk-stage-domain)
      (nvk-stage-vol)))
  (princ))

(defun C:НВК-ПЛАН ( / )
  (if (not (nvk-dll-zagruzit))
    (princ "\n[НВК] без DLL.")
    (progn
      (if (null *nvk-pipe-ss*) (nvk-stage-input))
      (nvk-stage-domain)
      (nvk-stage-plan)))
  (princ))

(defun C:НВК-ПОСТРОИТЬ ( / )
  (if (not (nvk-dll-zagruzit))
    (princ "\n[НВК] без DLL.")
    (nvk-progon))
  (princ))

(defun C:НВК-ПРОГОН ( / ) (C:НВК-ПОСТРОИТЬ))
(defun C:НВК-ОБНОВИТЬ ( / ) (C:НВК-ПОСТРОИТЬ))

(defun C:НВК-ОЧИСТИТЬ ( / r)
  (if (not (nvk-dll-zagruzit))
    (princ "\n[НВК] без DLL.")
    (progn
      (setq r (vl-catch-all-apply 'nvk-clean nil))
      (if (vl-catch-all-error-p r)
        (princ (strcat "\n[НВК] " (vl-catch-all-error-message r)))
        (princ (strcat "\n" (if r (vl-princ-to-string r) "готово"))))))
  (princ))

(defun C:НВК-ДВИГАТЬ ( / r)
  (if (not (nvk-dll-zagruzit))
    (princ "\n[НВК] без DLL.")
    (progn
      (nvk-layout-send)
      (setq r (vl-catch-all-apply 'nvk-move nil))
      (cond
        ((vl-catch-all-error-p r)
         (princ (strcat "\n[НВК] " (vl-catch-all-error-message r))))
        (t
         (nvk-layout-pull)
         (vl-catch-all-apply 'nvk-nod-sohranit nil)
         (princ "\n[НВК] точка записана в NOD. Обновить — перестроит на месте.")))))
  (princ))

(defun C:NVKMOVE () (C:НВК-ДВИГАТЬ))

(defun C:НВК-СБРОС ( / )
  (setq *nvk-cs-ins* nil
        *nvk-ep-ins* nil
        *nvk-vol-ins* nil
        *nvk-ep-lpts* (list nil nil nil nil nil)
        *nvk-cs-lpts* (list nil nil nil nil nil)
        *nvk-scatter-vals* ""
        *nvk-scatter-l2* ""
        *nvk-scatter-l3* ""
        *nvk-scatter-l4* ""
        *nvk-scatter-l5* ""
        *nvk-latoff-vals* ""
        *nvk-plan-tgt* ""
        *nvk-plan-lat* "")
  (vl-catch-all-apply 'nvk-cache-put
    (list "FRESH" "1"
          "SCATTER" "" "SCATTER2" "" "SCATTER3" "" "SCATTER4" "" "SCATTER5" ""
          "LATOFF" "" "PLAN_TGT" "" "PLAN_LAT" ""))
  (vl-catch-all-apply 'nvk-nod-sohranit nil)
  (princ "\n[НВК] точки вставки сброшены. Трубы и TIN на месте.")
  (princ))

(defun C:NVKINFO () (C:НВК-ИНФО))

(princ "\n  nvk-commands.lsp")
(princ)
